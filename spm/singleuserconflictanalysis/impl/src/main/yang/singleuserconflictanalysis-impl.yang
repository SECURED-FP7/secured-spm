module singleuserconflictanalysis-impl {
    yang-version 1;
    namespace "urn:opendaylight:params:xml:ns:yang:singleuserconflictanalysis:impl";
    prefix "singleuserconflictanalysis-impl";

    import config { prefix config; revision-date 2013-04-05; }
    import opendaylight-md-sal-binding { prefix md-sal-binding; revision-date 2013-10-28;}

    description
        "Service definition for singleuserconflictanalysis project";

    revision "2014-12-10" {
        description
            "Initial revision";
    }

    identity singleuserconflictanalysis {
        base config:module-type;
        config:java-name-prefix Singleuserconflictanalysis;
    }

    augment "/config:modules/config:module/config:configuration" {
        case singleuserconflictanalysis {
            when "/config:modules/config:module/config:type = 'singleuserconflictanalysis'";
            container broker {
                uses config:service-ref {
                    refine type {
                        mandatory true;
                        config:required-identity md-sal-binding:binding-broker-osgi-registry;
                    }
                }
            }
        }
    }
}
