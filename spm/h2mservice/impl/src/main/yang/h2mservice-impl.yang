module h2mservice-impl {
    yang-version 1;
    namespace "urn:opendaylight:params:xml:ns:yang:h2mservice:impl";
    prefix "h2mservice-impl";

    import config { prefix config; revision-date 2013-04-05; }
    import opendaylight-md-sal-binding { prefix md-sal-binding; revision-date 2013-10-28;}

    description
        "Service definition for h2mservice project";

    revision "2014-12-10" {
        description
            "Initial revision";
    }

    identity h2mservice {
        base config:module-type;
        config:java-name-prefix H2mservice;
    }

    augment "/config:modules/config:module/config:configuration" {
        case h2mservice {
            when "/config:modules/config:module/config:type = 'h2mservice'";
            container broker {
                uses config:service-ref {
                    refine type {
                        mandatory true;
                        config:required-identity md-sal-binding:binding-broker-osgi-registry;
                    }
                }
            }
        }
    }
}
