module m2lservice-impl {
    yang-version 1;
    namespace "urn:opendaylight:params:xml:ns:yang:m2lservice:impl";
    prefix "m2lservice-impl";

    import config { prefix config; revision-date 2013-04-05; }
    import opendaylight-md-sal-binding { prefix md-sal-binding; revision-date 2013-10-28;}

    description
        "Service definition for m2lservice project";

    revision "2014-12-10" {
        description
            "Initial revision";
    }

    identity m2lservice {
        base config:module-type;
        config:java-name-prefix M2lservice;
    }

    augment "/config:modules/config:module/config:configuration" {
        case m2lservice {
            when "/config:modules/config:module/config:type = 'm2lservice'";
            container broker {
                uses config:service-ref {
                    refine type {
                        mandatory true;
                        config:required-identity md-sal-binding:binding-broker-osgi-registry;
                    }
                }
            }
        }
    }
}
